-- **********************************************************
-- OPENWRT-WIRELESS-MIB
--
-- OpenWrt wireless metrics exported by the OpenWrt SNMP metrics agent.
-- The agent discovers radios/VAPs live (hostapd/iwinfo) at request time and
-- serves this subtree as a net-snmp AgentX subagent, so no per-interface or
-- per-metric snmpd configuration is required.
--
-- Registers under OPENWRT-MIB at { openwrtObjects 10 }
--   -> OID base .1.3.6.1.4.1.66510.1.10
--
-- Rows in openwrtWirelessInterfaceTable are indexed by IF-MIB ifIndex so the
-- table joins directly onto the standard ifTable/ifXTable for the same VAP.
-- **********************************************************

OPENWRT-WIRELESS-MIB DEFINITIONS ::= BEGIN

IMPORTS
    MODULE-IDENTITY, OBJECT-TYPE,
    Integer32, Unsigned32
        FROM SNMPv2-SMI
    DisplayString, PhysAddress, TEXTUAL-CONVENTION
        FROM SNMPv2-TC
    MODULE-COMPLIANCE, OBJECT-GROUP
        FROM SNMPv2-CONF
    InterfaceIndex
        FROM IF-MIB
    openwrtObjects, openwrtConformance
        FROM OPENWRT-MIB;

openwrtWirelessMIB MODULE-IDENTITY
    LAST-UPDATED "202610170000Z"
    ORGANIZATION "OpenWrt"
    CONTACT-INFO
        "       OpenWrt Project
                https://openwrt.org
                https://github.com/openwrt/openwrt
        "
    DESCRIPTION
        "MIB module describing OpenWrt wireless metrics (aggregate scalars,
         a per-interface table, and a per-radio-link table for multi-link
         interfaces) exported by the OpenWrt SNMP metrics agent's
         AgentX subagent."
    REVISION "202610170000Z"
    DESCRIPTION
        "Bitrates and channel utilisation are now reported in tenths of
         their unit (OpenwrtTenths), so Wi-Fi rates such as 72.2 Mbit/s
         and utilisation such as 89.6 percent keep their fractional part
         instead of being truncated to a whole number."
    REVISION "202609150000Z"
    DESCRIPTION
        "Added openwrtWirelessLinkTable: per-radio-link channel, transmit
         power and channel utilisation for 802.11be Multi-Link Operation
         (MLO/MLD) interfaces, queried directly over nl80211 rather than
         through the same path as the single-radio columns below, which
         cannot represent more than one radio per row."
    REVISION "202609120000Z"
    DESCRIPTION
        "Initial version: wireless aggregate scalars and per-interface table,
         including per-interface channel utilisation and transmit power.
         Radio-scoped objects are defined as absent on interfaces that span
         several radio links, so 802.11be multi-link devices are representable
         without reporting a misleading single value."
    ::= { openwrtObjects 10 }

-- **********************************************************
-- Textual conventions
-- **********************************************************

OpenwrtTenths ::= TEXTUAL-CONVENTION
    DISPLAY-HINT "d-1"
    STATUS       current
    DESCRIPTION
        "A non-negative quantity transmitted as an integer count of tenths
         of the unit given by the object's UNITS clause, so 722 for an object
         measured in Mbit/s is 72.2 Mbit/s. A manager should divide by 10."
    SYNTAX       Unsigned32

-- **********************************************************
-- Aggregate scalars
-- **********************************************************

openwrtWirelessInterfaceCount OBJECT-TYPE
    SYNTAX      Unsigned32
    MAX-ACCESS  read-only
    STATUS      current
    DESCRIPTION
        "Number of active wireless interfaces exported in
         openwrtWirelessInterfaceTable."
    ::= { openwrtWirelessMIB 1 }

openwrtWirelessClientCount OBJECT-TYPE
    SYNTAX      Unsigned32
    MAX-ACCESS  read-only
    STATUS      current
    DESCRIPTION
        "Aggregate count of unique wireless clients served by this device
         across its AP/master interfaces. MLO/MLD-related addresses are
         de-duplicated so a single client associated over multiple links
         counts once. Upstream associations on client/STA-mode interfaces are
         excluded (this device's own uplink is not one of its clients)."
    ::= { openwrtWirelessMIB 2 }

-- **********************************************************
-- Wireless interface table
-- **********************************************************

openwrtWirelessInterfaceTable OBJECT-TYPE
    SYNTAX      SEQUENCE OF OpenwrtWirelessInterfaceEntry
    MAX-ACCESS  not-accessible
    STATUS      current
    DESCRIPTION
        "OpenWrt wireless interfaces and their per-interface metrics."
    ::= { openwrtWirelessMIB 3 }

openwrtWirelessInterfaceEntry OBJECT-TYPE
    SYNTAX      OpenwrtWirelessInterfaceEntry
    MAX-ACCESS  not-accessible
    STATUS      current
    DESCRIPTION
        "Metrics for one OpenWrt wireless interface. Rows are indexed by the
         corresponding IF-MIB ifIndex, so that this table joins directly onto
         the standard interface table for the same VAP."
    INDEX { openwrtWlIfaceIfIndex }
    ::= { openwrtWirelessInterfaceTable 1 }

OpenwrtWirelessInterfaceEntry ::= SEQUENCE {
    openwrtWlIfaceIfIndex     InterfaceIndex,
    openwrtWlIfaceName        DisplayString,
    openwrtWlIfaceLabel       DisplayString,
    openwrtWlIfaceClients     Unsigned32,
    openwrtWlIfaceFrequency   Unsigned32,
    openwrtWlIfaceNoiseFloor  Integer32,
    openwrtWlIfaceTxRateMin   Unsigned32,
    openwrtWlIfaceTxRateAvg   Unsigned32,
    openwrtWlIfaceTxRateMax   Unsigned32,
    openwrtWlIfaceRxRateMin   Unsigned32,
    openwrtWlIfaceRxRateAvg   Unsigned32,
    openwrtWlIfaceRxRateMax   Unsigned32,
    openwrtWlIfaceSnrMin      Integer32,
    openwrtWlIfaceSnrAvg      Integer32,
    openwrtWlIfaceSnrMax      Integer32,
    openwrtWlIfaceChannelUtil Unsigned32,
    openwrtWlIfaceTxPower     Integer32
}

openwrtWlIfaceIfIndex OBJECT-TYPE
    SYNTAX      InterfaceIndex
    MAX-ACCESS  not-accessible
    STATUS      current
    DESCRIPTION
        "The kernel interface index (IF-MIB ifIndex) of this wireless
         interface, taken from /sys/class/net/<iface>/ifindex. Used as the
         table index so rows align with the standard ifTable/ifXTable."
    ::= { openwrtWirelessInterfaceEntry 1 }

openwrtWlIfaceName OBJECT-TYPE
    SYNTAX      DisplayString
    MAX-ACCESS  read-only
    STATUS      current
    DESCRIPTION
        "OpenWrt wireless interface name, for example wlan0 or phy0-ap0."
    ::= { openwrtWirelessInterfaceEntry 2 }

openwrtWlIfaceLabel OBJECT-TYPE
    SYNTAX      DisplayString
    MAX-ACCESS  read-only
    STATUS      current
    DESCRIPTION
        "Display label for the wireless interface: its SSID, or the
         interface name itself if it has none (a monitor interface, or a
         VAP that is currently down). Not necessarily unique - two VAPs
         broadcasting the same SSID on different bands get identical
         labels here; use openwrtWlIfaceIfIndex to tell them apart."
    ::= { openwrtWirelessInterfaceEntry 3 }

openwrtWlIfaceClients OBJECT-TYPE
    SYNTAX      Unsigned32
    MAX-ACCESS  read-only
    STATUS      current
    DESCRIPTION
        "Number of stations associated with this wireless interface.
         For an AP/master interface this is the count of connected clients.
         For a client/STA-mode interface (e.g. a wireless uplink or backhaul)
         this is the number of upstream associations, which is its peer count:
         1 while associated to an AP, 0 when there is no peer (not associated /
         link down) - so it doubles as a backhaul link-up indicator."
    ::= { openwrtWirelessInterfaceEntry 4 }

openwrtWlIfaceFrequency OBJECT-TYPE
    SYNTAX      Unsigned32
    UNITS       "MHz"
    MAX-ACCESS  read-only
    STATUS      current
    DESCRIPTION
        "Current channel centre frequency in MHz.

         Absent for an interface that spans several radio links (an
         802.11be multi-link device), which has no single value for
         this object; agents report noSuchInstance in that case. See
         openwrtWirelessLinkTable for that interface's per-link frequency
         instead."
    ::= { openwrtWirelessInterfaceEntry 5 }

openwrtWlIfaceNoiseFloor OBJECT-TYPE
    SYNTAX      Integer32
    UNITS       "dBm"
    MAX-ACCESS  read-only
    STATUS      current
    DESCRIPTION
        "Noise floor for this wireless interface in dBm (typically
         negative).

         Absent if the driver reports no noise measurement, or for an
         interface that spans several radio links (an 802.11be multi-link
         device), which has no single value for this object; agents report
         noSuchInstance in those cases. Unlike frequency, transmit power
         and channel utilisation, this has no per-link equivalent in
         openwrtWirelessLinkTable: nl80211 has no per-link noise attribute,
         only a device-wide one."
    ::= { openwrtWirelessInterfaceEntry 6 }

openwrtWlIfaceTxRateMin OBJECT-TYPE
    SYNTAX      OpenwrtTenths
    UNITS       "Mbit/s"
    MAX-ACCESS  read-only
    STATUS      current
    DESCRIPTION
        "Minimum transmit bitrate across associated stations, in tenths of
         Mbit/s (722 is 72.2 Mbit/s). Expressed in Mbit/s rather than
         bit/s so that Wi-Fi 6E/7 rates (multi-Gbit/s) do not overflow
         Unsigned32."
    ::= { openwrtWirelessInterfaceEntry 7 }

openwrtWlIfaceTxRateAvg OBJECT-TYPE
    SYNTAX      OpenwrtTenths
    UNITS       "Mbit/s"
    MAX-ACCESS  read-only
    STATUS      current
    DESCRIPTION
        "Average transmit bitrate across associated stations, in tenths of
         Mbit/s (722 is 72.2 Mbit/s)."
    ::= { openwrtWirelessInterfaceEntry 8 }

openwrtWlIfaceTxRateMax OBJECT-TYPE
    SYNTAX      OpenwrtTenths
    UNITS       "Mbit/s"
    MAX-ACCESS  read-only
    STATUS      current
    DESCRIPTION
        "Maximum transmit bitrate across associated stations, in tenths of
         Mbit/s (722 is 72.2 Mbit/s)."
    ::= { openwrtWirelessInterfaceEntry 9 }

openwrtWlIfaceRxRateMin OBJECT-TYPE
    SYNTAX      OpenwrtTenths
    UNITS       "Mbit/s"
    MAX-ACCESS  read-only
    STATUS      current
    DESCRIPTION
        "Minimum receive bitrate across associated stations, in tenths of
         Mbit/s (722 is 72.2 Mbit/s)."
    ::= { openwrtWirelessInterfaceEntry 10 }

openwrtWlIfaceRxRateAvg OBJECT-TYPE
    SYNTAX      OpenwrtTenths
    UNITS       "Mbit/s"
    MAX-ACCESS  read-only
    STATUS      current
    DESCRIPTION
        "Average receive bitrate across associated stations, in tenths of
         Mbit/s (722 is 72.2 Mbit/s)."
    ::= { openwrtWirelessInterfaceEntry 11 }

openwrtWlIfaceRxRateMax OBJECT-TYPE
    SYNTAX      OpenwrtTenths
    UNITS       "Mbit/s"
    MAX-ACCESS  read-only
    STATUS      current
    DESCRIPTION
        "Maximum receive bitrate across associated stations, in tenths of
         Mbit/s (722 is 72.2 Mbit/s)."
    ::= { openwrtWirelessInterfaceEntry 12 }

openwrtWlIfaceSnrMin OBJECT-TYPE
    SYNTAX      Integer32
    UNITS       "dB"
    MAX-ACCESS  read-only
    STATUS      current
    DESCRIPTION
        "Minimum signal-to-noise ratio across associated stations, in dB."
    ::= { openwrtWirelessInterfaceEntry 13 }

openwrtWlIfaceSnrAvg OBJECT-TYPE
    SYNTAX      Integer32
    UNITS       "dB"
    MAX-ACCESS  read-only
    STATUS      current
    DESCRIPTION
        "Average signal-to-noise ratio across associated stations, in dB."
    ::= { openwrtWirelessInterfaceEntry 14 }

openwrtWlIfaceSnrMax OBJECT-TYPE
    SYNTAX      Integer32
    UNITS       "dB"
    MAX-ACCESS  read-only
    STATUS      current
    DESCRIPTION
        "Maximum signal-to-noise ratio across associated stations, in dB."
    ::= { openwrtWirelessInterfaceEntry 15 }

openwrtWlIfaceChannelUtil OBJECT-TYPE
    SYNTAX      OpenwrtTenths
    UNITS       "percent"
    MAX-ACCESS  read-only
    STATUS      current
    DESCRIPTION
        "Channel airtime utilisation for this interface's radio, in tenths
         of a percent (0-1000; 896 is 89.6 percent). This is the fraction of time the channel is
         observed busy. Absent if the driver reports no survey data for
         the operating channel, or for a multi-link interface, which has no
         single radio; agents report noSuchInstance in those cases. See
         openwrtWirelessLinkTable for a multi-link interface's per-link
         channel utilisation instead."
    ::= { openwrtWirelessInterfaceEntry 16 }

openwrtWlIfaceTxPower OBJECT-TYPE
    SYNTAX      Integer32
    UNITS       "dBm"
    MAX-ACCESS  read-only
    STATUS      current
    DESCRIPTION
        "Current transmit power for this wireless interface in dBm.

         Absent if the driver reports no transmit power, or for an
         interface that spans several radio links (an 802.11be multi-link
         device), which has no single value for this object; agents report
         noSuchInstance in those cases. See openwrtWirelessLinkTable for
         that interface's per-link transmit power instead."
    ::= { openwrtWirelessInterfaceEntry 17 }

-- **********************************************************
-- Wireless link table (802.11be Multi-Link Operation)
-- **********************************************************

openwrtWirelessLinkTable OBJECT-TYPE
    SYNTAX      SEQUENCE OF OpenwrtWirelessLinkEntry
    MAX-ACCESS  not-accessible
    STATUS      current
    DESCRIPTION
        "Per-radio-link metrics for wireless interfaces using 802.11be
         Multi-Link Operation (MLO/MLD), where a single netdev spans
         several radio links and so has no single channel, transmit power
         or channel utilisation of its own - see openwrtWlIfaceFrequency
         and the related objects in openwrtWirelessInterfaceTable, which
         are defined as absent for such an interface. Each row here is one
         link of one such interface; several rows share one ifIndex. This
         table has no rows at all on a device with no multi-link
         interface, rather than being present but empty."
    ::= { openwrtWirelessMIB 4 }

openwrtWirelessLinkEntry OBJECT-TYPE
    SYNTAX      OpenwrtWirelessLinkEntry
    MAX-ACCESS  not-accessible
    STATUS      current
    DESCRIPTION
        "Metrics for one radio link of one multi-link wireless interface."
    INDEX { openwrtWlLinkIfIndex, openwrtWlLinkId }
    ::= { openwrtWirelessLinkTable 1 }

OpenwrtWirelessLinkEntry ::= SEQUENCE {
    openwrtWlLinkIfIndex     InterfaceIndex,
    openwrtWlLinkId          Integer32,
    openwrtWlLinkAddress     PhysAddress,
    openwrtWlLinkFrequency   Unsigned32,
    openwrtWlLinkTxPower     Integer32,
    openwrtWlLinkChannelUtil Unsigned32
}

openwrtWlLinkIfIndex OBJECT-TYPE
    SYNTAX      InterfaceIndex
    MAX-ACCESS  not-accessible
    STATUS      current
    DESCRIPTION
        "The ifIndex of the parent multi-link wireless interface - the same
         value as openwrtWlIfaceIfIndex for that interface's row in
         openwrtWirelessInterfaceTable."
    ::= { openwrtWirelessLinkEntry 1 }

openwrtWlLinkId OBJECT-TYPE
    SYNTAX      Integer32 (0..15)
    MAX-ACCESS  not-accessible
    STATUS      current
    DESCRIPTION
        "The link ID nl80211 assigns this radio link within its MLD
         (NL80211_ATTR_MLO_LINK_ID), stable for the life of the link."
    ::= { openwrtWirelessLinkEntry 2 }

openwrtWlLinkAddress OBJECT-TYPE
    SYNTAX      PhysAddress
    MAX-ACCESS  read-only
    STATUS      current
    DESCRIPTION
        "The MAC address this specific link transmits from. Distinct from
         the MLD address associations use, and from the other links'
         addresses on the same interface."
    ::= { openwrtWirelessLinkEntry 3 }

openwrtWlLinkFrequency OBJECT-TYPE
    SYNTAX      Unsigned32
    UNITS       "MHz"
    MAX-ACCESS  read-only
    STATUS      current
    DESCRIPTION
        "Current channel centre frequency in MHz for this link."
    ::= { openwrtWirelessLinkEntry 4 }

openwrtWlLinkTxPower OBJECT-TYPE
    SYNTAX      Integer32
    UNITS       "dBm"
    MAX-ACCESS  read-only
    STATUS      current
    DESCRIPTION
        "Current transmit power for this link in dBm. Absent if the
         kernel did not report a transmit power for this link; agents
         report noSuchInstance in that case."
    ::= { openwrtWirelessLinkEntry 5 }

openwrtWlLinkChannelUtil OBJECT-TYPE
    SYNTAX      OpenwrtTenths
    UNITS       "percent"
    MAX-ACCESS  read-only
    STATUS      current
    DESCRIPTION
        "Channel airtime utilisation for this link's radio, in tenths of a
         percent (0-1000), from the same survey data as
         openwrtWlIfaceChannelUtil. Absent if the driver reports no survey
         data for this link's operating channel; agents report
         noSuchInstance in that case."
    ::= { openwrtWirelessLinkEntry 6 }

-- **********************************************************
-- Conformance
-- **********************************************************

openwrtWirelessConformance OBJECT IDENTIFIER ::= { openwrtConformance 10 }
openwrtWirelessCompliances  OBJECT IDENTIFIER ::= { openwrtWirelessConformance 1 }
openwrtWirelessGroups       OBJECT IDENTIFIER ::= { openwrtWirelessConformance 2 }

openwrtWirelessScalarGroup OBJECT-GROUP
    OBJECTS {
        openwrtWirelessInterfaceCount,
        openwrtWirelessClientCount
    }
    STATUS  current
    DESCRIPTION
        "Aggregate wireless scalars."
    ::= { openwrtWirelessGroups 1 }

openwrtWirelessInterfaceGroup OBJECT-GROUP
    OBJECTS {
        openwrtWlIfaceName,
        openwrtWlIfaceLabel,
        openwrtWlIfaceClients,
        openwrtWlIfaceFrequency,
        openwrtWlIfaceNoiseFloor,
        openwrtWlIfaceTxRateMin,
        openwrtWlIfaceTxRateAvg,
        openwrtWlIfaceTxRateMax,
        openwrtWlIfaceRxRateMin,
        openwrtWlIfaceRxRateAvg,
        openwrtWlIfaceRxRateMax,
        openwrtWlIfaceSnrMin,
        openwrtWlIfaceSnrAvg,
        openwrtWlIfaceSnrMax,
        openwrtWlIfaceChannelUtil,
        openwrtWlIfaceTxPower
    }
    STATUS  current
    DESCRIPTION
        "Per-interface wireless metrics."
    ::= { openwrtWirelessGroups 2 }

openwrtWirelessLinkGroup OBJECT-GROUP
    OBJECTS {
        openwrtWlLinkAddress,
        openwrtWlLinkFrequency,
        openwrtWlLinkTxPower,
        openwrtWlLinkChannelUtil
    }
    STATUS  current
    DESCRIPTION
        "Per-radio-link metrics for 802.11be Multi-Link Operation
         interfaces. Optional: a device with no multi-link interface has
         no rows to report and so cannot implement this group."
    ::= { openwrtWirelessGroups 3 }

openwrtWirelessCompliance MODULE-COMPLIANCE
    STATUS  current
    DESCRIPTION
        "Compliance statement for OpenWrt wireless monitoring agents."
    MODULE  -- this module
    MANDATORY-GROUPS {
        openwrtWirelessScalarGroup,
        openwrtWirelessInterfaceGroup
    }
    GROUP   openwrtWirelessLinkGroup
    DESCRIPTION
        "Implemented only by agents that have at least one multi-link
         (802.11be MLO/MLD) wireless interface to report."
    ::= { openwrtWirelessCompliances 1 }

END
